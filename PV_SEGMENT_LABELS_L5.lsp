;;; PV_SEGMENT_LABELS_L5.lsp - segment labels for the NSITC L5 blue-line PV layout (PV_LAYOUT_L5_BLUE_LINE.lsp, 6915 modules).
;;; A segment is one unbroken run of tables (20 mm joints). Wherever the run is broken (gap > 2 ft; the real breaks are 37 ft or more) a new segment starts.
;;; Command PVSEGMENTS -> 14 segments: segment outline + 2-line label (segment no., area, modules, tables, kWp) + a per-segment table east of the site.
;;; Layers PV-SEG-OUTLINE and PV-SEG-TEXT (magenta). Re-running erases only these two layers; PVLAYOUT and the panels are not touched. One U undoes it.
(defun pvSegLayer (n c)
  (if (not (tblsearch "LAYER" n))
    (entmake (list (cons 0 "LAYER") (cons 100 "AcDbSymbolTableRecord") (cons 100 "AcDbLayerTableRecord")
                   (cons 2 n) (cons 70 0) (cons 62 c) (cons 6 "Continuous")))))
(defun pvSegPL (pts)
  (entmake (append (list (cons 0 "LWPOLYLINE") (cons 100 "AcDbEntity") (cons 8 "PV-SEG-OUTLINE") (cons 100 "AcDbPolyline")
                         (cons 90 (length pts)) (cons 70 1) (cons 43 0.5))
                   (mapcar '(lambda (p) (list 10 (car p) (cadr p))) pts))))
(defun pvSegT (s p r h)
  (entmake (list (cons 0 "TEXT") (cons 8 "PV-SEG-TEXT") (list 10 (car p) (cadr p) 0.0) (list 11 (car p) (cadr p) 0.0)
                 (cons 40 h) (cons 1 s) (cons 50 r) (cons 72 1) (cons 73 2))))
(defun pvSegTL (s x y h)
  (entmake (list (cons 0 "TEXT") (cons 8 "PV-SEG-TEXT") (list 10 x y 0.0) (cons 40 h) (cons 1 s) (cons 50 0.0))))
(defun pvSeg01 ()
  (pvSegPL (list (list 1474818.6675 11419265.3380) (list 1474809.2349 11419285.1551) (list 1474816.1775 11419288.4597) (list 1474816.1175 11419288.5904) (list 1474823.1076 11419291.7983) (list 1474823.0563 11419291.9145) (list 1474830.0920 11419295.0248) (list 1474830.0410 11419295.1445) (list 1474837.1231 11419298.1574) (list 1474837.0723 11419298.2815) (list 1474844.2010 11419301.1961) (list 1474844.1585 11419301.3046) (list 1474851.3244 11419304.1157) (list 1474851.2814 11419304.2298) (list 1474858.4875 11419306.9408) (list 1474858.4449 11419307.0588) (list 1474865.6897 11419309.6691) (list 1474865.6514 11419309.7803) (list 1474872.9335 11419312.2893) (list 1474872.8986 11419312.3955) (list 1474880.2221 11419314.8044) (list 1474880.1887 11419314.9114) (list 1474887.5423 11419317.2142) (list 1474887.5096 11419317.3241) (list 1474894.8953 11419319.5235) (list 1474894.8669 11419319.6239) (list 1474902.2839 11419321.7200) (list 1474902.2560 11419321.8243) (list 1474909.7030 11419323.8167) (list 1474909.6765 11419323.9214) (list 1474924.6188 11419327.7806) (list 1474939.6615 11419331.2176) (list 1474954.8004 11419334.2269) (list 1474970.0334 11419336.7875) (list 1474985.3283 11419338.9201) (list 1475000.6877 11419340.6132) (list 1475016.0900 11419341.8562) (list 1475031.5215 11419342.6650) (list 1475046.9819 11419343.0239) (list 1475062.4395 11419342.9376) (list 1475077.8999 11419342.4130) (list 1475093.3314 11419341.4320) (list 1475108.7332 11419340.0100) (list 1475124.0920 11419338.1461) (list 1475139.3842 11419335.8320) (list 1475154.6142 11419333.0790) (list 1475169.7480 11419329.8832) (list 1475178.8069 11419327.7509) (list 1475193.7870 11419323.8610) (list 1475208.6395 11419319.5406) (list 1475223.3603 11419314.7854) (list 1475237.9411 11419309.6058) (list 1475252.3582 11419304.0090) (list 1475266.6117 11419297.9886) (list 1475280.6787 11419291.5711) (list 1475287.6371 11419288.2036) (list 1475301.4140 11419281.1747) (list 1475314.9730 11419273.7572) (list 1475321.6690 11419269.9017) (list 1475334.9012 11419261.9166) (list 1475334.8473 11419261.8269) (list 1475341.3278 11419257.7316) (list 1476457.7235 11418566.1421) (list 1476446.1815 11418547.4746) (list 1475328.1988 11419240.0453) (list 1475321.9770 11419244.0774) (list 1475309.2555 11419251.7037) (list 1475302.8165 11419255.3866) (list 1475289.7784 11419262.4700) (list 1475276.5385 11419269.1755) (list 1475269.8485 11419272.3891) (list 1475256.3241 11419278.5103) (list 1475242.6290 11419284.2460) (list 1475228.7698 11419289.5779) (list 1475221.7842 11419292.0959) (list 1475207.3342 11419296.9307) (list 1475193.8416 11419301.0298) (list 1475179.6941 11419304.8950) (list 1475158.9367 11419309.7798) (list 1475145.0130 11419312.5506) (list 1475130.3974 11419315.0269) (list 1475122.7405 11419316.1596) (list 1475108.0034 11419317.9941) (list 1475093.2219 11419319.4042) (list 1475078.4076 11419320.3908) (list 1475070.9920 11419320.7177) (list 1475056.1527 11419321.0592) (list 1475041.3122 11419320.9654) (list 1475026.4835 11419320.4532) (list 1475011.6792 11419319.5093) (list 1475004.2897 11419318.8809) (list 1474989.5454 11419317.2986) (list 1474974.8567 11419315.2929) (list 1474960.2337 11419312.8782) (list 1474945.6933 11419310.0300) (list 1474931.2444 11419306.7709) (list 1474916.8972 11419303.1084) (list 1474902.6702 11419299.0219) (list 1474888.5697 11419294.5375) (list 1474874.6082 11419289.6526) (list 1474860.8017 11419284.3622) (list 1474847.1538 11419278.6924) (list 1474847.1966 11419278.5919) (list 1474840.3993 11419275.7001) (list 1474840.4419 11419275.6038) (list 1474833.6875 11419272.6178) (list 1474833.7301 11419272.5248) (list 1474827.0195 11419269.4452) (list 1474827.0706 11419269.3378)))
  (pvSegT "SEG 01 - CT-1 NORTH A" (list 1475682.7531 11419073.8641) -0.55376389 7.0)
  (pvSegT "1250 MODULES = 250 TABLES = 775.0 kWp" (list 1475677.7571 11419065.7839) -0.55376389 5.5))
(defun pvSeg02 ()
  (pvSegPL (list (list 1476775.1313 11418344.0834) (list 1476786.6994 11418362.7348) (list 1477014.0529 11418222.1120) (list 1477002.4849 11418203.4606)))
  (pvSegT "SEG 02 - CT-2 NORTH-EAST" (list 1476909.6333 11418314.3423) -0.55515709 7.0)
  (pvSegT "180 MODULES = 36 TABLES = 111.6 kWp" (list 1476904.6261 11418306.2690) -0.55515709 5.5))
(defun pvSeg03 ()
  (pvSegPL (list (list 1478185.7235 11417109.8460) (list 1478202.1247 11417124.4300) (list 1478859.8711 11416384.8008) (list 1478843.4699 11416370.2167)))
  (pvSegT "SEG 03 - CT-3 EAST" (list 1478546.1238 11416772.9981) -0.84397306 7.0)
  (pvSegT "670 MODULES = 134 TABLES = 415.4 kWp" (list 1478539.0246 11416766.6853) -0.84397306 5.5))
(defun pvSeg04 ()
  (pvSegPL (list (list 1478978.5227 11416218.3377) (list 1478994.9238 11416232.9218) (list 1479183.0136 11416021.3845) (list 1479196.8514 11416005.0208) (list 1479207.3714 11415991.6549) (list 1479190.0304 11415978.2020) (list 1479180.2556 11415990.6310) (list 1479170.9072 11416001.8475) (list 1479165.8349 11416007.6763)))
  (pvSegT "SEG 04 - CT-4 SOUTH-EAST CURVE (1 OF 3)" (list 1479118.6809 11416129.1051) -0.84397306 7.0)
  (pvSegT "215 MODULES = 43 TABLES = 133.3 kWp" (list 1479111.5816 11416122.7924) -0.84397306 5.5))
(defun pvSeg05 ()
  (pvSegPL (list (list 1478977.0119 11415118.3134) (list 1478962.9828 11415135.1917) (list 1479105.0781 11415253.3007) (list 1479111.8568 11415258.9809) (list 1479122.9557 11415268.6608) (list 1479133.9137 11415278.7800) (list 1479144.5029 11415289.1214) (list 1479154.8766 11415299.8477) (list 1479164.8553 11415310.7610) (list 1479169.7014 11415316.2912) (list 1479179.1604 11415327.5563) (list 1479188.3941 11415339.2003) (list 1479197.2318 11415351.0209) (list 1479201.5507 11415357.0556) (list 1479209.8448 11415369.1861) (list 1479213.9365 11415375.4473) (list 1479221.6645 11415387.8372) (list 1479225.4905 11415394.2709) (list 1479232.7388 11415407.0600) (list 1479236.2319 11415413.5426) (list 1479239.6821 11415420.1660) (list 1479246.2286 11415433.4026) (list 1479252.3754 11415446.7728) (list 1479258.2070 11415460.4454) (list 1479260.9433 11415467.2635) (list 1479266.1829 11415481.1475) (list 1479271.0295 11415495.1823) (list 1479275.4742 11415509.3316) (list 1479277.5483 11415516.4538) (list 1479281.3781 11415530.7361) (list 1479284.7985 11415545.0660) (list 1479286.3878 11415552.4235) (list 1479289.2183 11415567.0098) (list 1479290.4791 11415574.3200) (list 1479292.6741 11415588.9174) (list 1479294.4630 11415603.5594) (list 1479295.2045 11415610.9346) (list 1479296.3709 11415625.6363) (list 1479297.1277 11415640.3624) (list 1479297.3485 11415647.7640) (list 1479297.4812 11415662.5678) (list 1479297.1962 11415677.3483) (list 1479296.4943 11415692.1090) (list 1479295.3915 11415706.6977) (list 1479293.8384 11415721.6051) (list 1479291.9168 11415736.0849) (list 1479289.5544 11415750.7221) (list 1479286.7966 11415765.2008) (list 1479285.2280 11415772.5796) (list 1479281.8552 11415786.9539) (list 1479278.0902 11415801.1797) (list 1479273.9182 11415815.3382) (list 1479269.2926 11415829.5311) (list 1479264.2940 11415843.5357) (list 1479258.9826 11415857.1790) (list 1479253.1893 11415870.9129) (list 1479247.0522 11415884.3796) (list 1479240.5691 11415897.6171) (list 1479233.2144 11415911.5967) (list 1479252.5711 11415921.9413) (list 1479259.7624 11415908.3092) (list 1479263.9154 11415899.9808) (list 1479270.4779 11415886.0390) (list 1479276.6502 11415871.9153) (list 1479282.4207 11415857.6290) (list 1479287.7875 11415843.1784) (list 1479292.2481 11415830.1159) (list 1479296.8408 11415815.4004) (list 1479301.0153 11415800.5696) (list 1479304.7722 11415785.6198) (list 1479308.1058 11415770.5763) (list 1479311.0161 11415755.4394) (list 1479313.4981 11415740.2305) (list 1479314.7878 11415731.0139) (list 1479316.5777 11415715.7048) (list 1479317.9402 11415700.3550) (list 1479318.8637 11415684.9686) (list 1479319.3573 11415669.5679) (list 1479319.4129 11415654.1523) (list 1479319.0958 11415640.3434) (list 1479318.6849 11415631.0460) (list 1479317.6554 11415615.6721) (list 1479316.1966 11415600.3320) (list 1479314.3025 11415585.0350) (list 1479311.9855 11415569.8032) (list 1479309.5384 11415556.2079) (list 1479306.4112 11415541.1141) (list 1479302.8561 11415526.1211) (list 1479298.8855 11415511.2276) (list 1479294.4964 11415496.4569) (list 1479289.6949 11415481.8098) (list 1479286.5939 11415473.0353) (list 1479281.7245 11415460.1174) (list 1479275.9025 11415445.8424) (list 1479269.6873 11415431.7458) (list 1479263.0725 11415417.8206) (list 1479256.0724 11415404.0956) (list 1479251.6578 11415395.9028) (list 1479244.8494 11415383.8853) (list 1479236.8975 11415370.6771) (list 1479228.5775 11415357.7109) (list 1479219.8924 11415344.9727) (list 1479214.4761 11415337.4048) (list 1479205.2310 11415325.0807) (list 1479195.6315 11415313.0165) (list 1479186.7492 11415302.4441) (list 1479180.6157 11415295.4448) (list 1479170.1949 11415284.0890) (list 1479159.4631 11415273.0308) (list 1479148.4185 11415262.2783) (list 1479138.2712 11415252.9067) (list 1479126.6887 11415242.7749)))
  (pvSegT "SEG 05 - CT-4 SOUTH-EAST CURVE (2 OF 3)" (list 1479295.8690 11415457.9367) 1.20307890 7.0)
  (pvSegT "615 MODULES = 123 TABLES = 381.3 kWp" (list 1479304.7339 11415454.5216) 1.20307890 5.5))
(defun pvSeg06 ()
  (pvSegPL (list (list 1478538.0168 11414792.5522) (list 1478529.5295 11414812.7922) (list 1478544.1230 11414818.9665) (list 1478564.4083 11414828.2760) (list 1478584.4547 11414838.3577) (list 1478597.5157 11414845.4224) (list 1478616.7701 11414856.5880) (list 1478629.4571 11414864.4570) (list 1478648.0802 11414876.7940) (list 1478666.3299 11414889.8442) (list 1478678.1307 11414898.8263) (list 1478689.7480 11414908.1139) (list 1478902.0778 11415084.5678) (list 1478916.1070 11415067.6895) (list 1478703.0672 11414890.6482) (list 1478691.0257 11414881.0438) (list 1478678.7446 11414871.7196) (list 1478666.2452 11414862.6903) (list 1478654.8506 11414854.8449) (list 1478641.9530 11414846.3883) (list 1478627.4963 11414837.4207) (list 1478608.8615 11414826.6132) (list 1478595.3029 11414819.2596) (list 1478581.5741 11414812.2302) (list 1478567.6843 11414805.5314) (list 1478552.1772 11414798.5284)))
  (pvSegT "SEG 06 - CT-4 SOUTH-EAST CURVE (3 OF 3)" (list 1478750.0796 11414911.4884) 0.69347523 7.0)
  (pvSegT "310 MODULES = 62 TABLES = 192.2 kWp" (list 1478756.1521 11414904.1826) 0.69347523 5.5))
(defun pvSeg07 ()
  (pvSegPL (list (list 1477571.1499 11414502.3657) (list 1477563.5968 11414503.9765) (list 1477568.1463 11414525.4472) (list 1477583.6248 11414522.2764) (list 1477598.2264 11414519.7186) (list 1477612.8628 11414517.5779) (list 1477627.5523 11414515.8502) (list 1477642.3547 11414514.5308) (list 1477657.1465 11414513.6322) (list 1477671.9814 11414513.1512) (list 1477686.7789 11414513.0886) (list 1477701.5790 11414513.4433) (list 1477716.3764 11414514.2153) (list 1477731.1819 11414515.4069) (list 1477745.9186 11414517.0130) (list 1477760.5994 11414519.0341) (list 1477775.2164 11414521.4683) (list 1477789.7801 11414524.3180) (list 1477804.2679 11414527.5801) (list 1477811.4166 11414529.3488) (list 1477825.7676 11414533.2233) (list 1477839.9217 11414537.4765) (list 1477846.9069 11414539.7371) (list 1477860.8967 11414544.5931) (list 1477874.8590 11414549.8871) (list 1478225.9125 11414690.8524) (list 1478234.0915 11414670.4859) (list 1477882.1287 11414529.1564) (list 1477861.9521 11414521.6653) (list 1477847.3017 11414516.7847) (list 1477830.9950 11414511.8849) (list 1477816.0811 11414507.8821) (list 1477801.0603 11414504.3013) (list 1477785.9446 11414501.1443) (list 1477770.7459 11414498.4147) (list 1477755.4762 11414496.1150) (list 1477740.1475 11414494.2469) (list 1477724.7703 11414492.8132) (list 1477709.3590 11414491.8138) (list 1477693.9267 11414491.2484) (list 1477678.4852 11414491.1182) (list 1477663.0464 11414491.4239) (list 1477647.6223 11414492.1643) (list 1477632.2252 11414493.3401) (list 1477616.8675 11414494.9493) (list 1477601.5613 11414496.9907) (list 1477586.3188 11414499.4631)))
  (pvSegT "SEG 07 - CT-5 SOUTH ARC" (list 1477919.2521 11414528.9663) 0.38187766 7.0)
  (pvSegT "465 MODULES = 93 TABLES = 288.3 kWp" (list 1477922.7924 11414520.1506) 0.38187766 5.5))
(defun pvSeg08 ()
  (pvSegPL (list (list 1477185.3756 11414677.5010) (list 1477195.3719 11414697.0399) (list 1477348.0429 11414618.9316) (list 1477347.9930 11414618.8340) (list 1477354.5560 11414615.4763) (list 1477354.3049 11414614.9855) (list 1477360.8679 11414611.6278) (list 1477350.8716 11414592.0890) (list 1477342.5865 11414596.3277) (list 1477342.8376 11414596.8185) (list 1477336.2746 11414600.1762) (list 1477336.3245 11414600.2738)))
  (pvSegT "SEG 08 - CT-6 SOUTH (1 OF 3)" (list 1477261.8993 11414622.6290) -0.47289368 7.0)
  (pvSegT "125 MODULES = 25 TABLES = 77.5 kWp" (list 1477257.5724 11414614.1716) -0.47289368 5.5))
(defun pvSeg09 ()
  (pvSegPL (list (list 1476417.3270 11415070.0041) (list 1476427.3233 11415089.5430) (list 1476433.8863 11415086.1853) (list 1476434.0645 11415086.5336) (list 1477164.2791 11414712.9473) (list 1477154.2827 11414693.4085) (list 1476425.7903 11415066.1137) (list 1476425.6121 11415065.7654)))
  (pvSegT "SEG 09 - CT-6 SOUTH (2 OF 3)" (list 1476782.8007 11414867.7414) -0.47289368 7.0)
  (pvSegT "560 MODULES = 112 TABLES = 347.2 kWp" (list 1476778.4738 11414859.2840) -0.47289368 5.5))
(defun pvSeg10 ()
  (pvSegPL (list (list 1475878.8497 11415344.7265) (list 1475888.8460 11415364.2654) (list 1475895.4090 11415360.9077) (list 1475895.6384 11415361.3561) (list 1476178.1633 11415217.5927) (list 1476192.9924 11415209.9591) (list 1476192.7721 11415209.5287) (list 1476199.3352 11415206.1709) (list 1476189.3389 11415186.6321) (list 1476181.0538 11415190.8708) (list 1476181.2740 11415191.3013) (list 1476163.3228 11415200.5241) (list 1475893.9738 11415337.6695) (list 1475893.9272 11415337.5785) (list 1475887.3642 11415340.9362) (list 1475887.1348 11415340.4878)))
  (pvSegT "SEG 10 - CT-6 SOUTH (3 OF 3)" (list 1476027.9782 11415253.7248) -0.47289368 7.0)
  (pvSegT "235 MODULES = 47 TABLES = 145.7 kWp" (list 1476023.6513 11415245.2673) -0.47289368 5.5))
(defun pvSeg11 ()
  (pvSegPL (list (list 1474775.4808 11416257.9941) (list 1474790.0725 11416274.3885) (list 1475556.9602 11415591.8263) (list 1475542.3685 11415575.4319)))
  (pvSegT "SEG 11 - CT-9 SOUTH-WEST" (list 1475149.6194 11415906.2581) -0.72728597 7.0)
  (pvSegT "695 MODULES = 139 TABLES = 430.9 kWp" (list 1475143.3034 11415899.1618) -0.72728597 5.5))
(defun pvSeg12 ()
  (pvSegPL (list (list 1474275.5401 11416702.9483) (list 1474290.1318 11416719.3426) (list 1474578.2837 11416462.8755) (list 1474563.6920 11416446.4812)))
  (pvSegT "SEG 12 - CT-7 WEST (1 OF 2)" (list 1474413.2412 11416561.6515) -0.72728597 7.0)
  (pvSegT "260 MODULES = 52 TABLES = 161.2 kWp" (list 1474406.9252 11416554.5552) -0.72728597 5.5))
(defun pvSeg13 ()
  (pvSegPL (list (list 1474043.5174 11417115.8893) (list 1474050.8786 11417774.1561) (list 1474051.2855 11417794.8620) (list 1474051.8198 11417809.9016) (list 1474053.0997 11417834.2348) (list 1474055.3943 11417864.2547) (list 1474058.2716 11417892.4399) (list 1474062.0919 11417922.3063) (list 1474066.6946 11417952.0606) (list 1474070.9896 11417976.0365) (list 1474076.6224 11418003.7993) (list 1474082.0128 11418027.5577) (list 1474103.3843 11418022.5624) (list 1474098.2619 11418000.0140) (list 1474092.3873 11417971.0561) (list 1474087.2764 11417941.9635) (list 1474082.9295 11417912.7389) (list 1474079.3535 11417883.4320) (list 1474076.5469 11417854.0378) (list 1474074.5149 11417824.6196) (list 1474073.4979 11417802.5070) (list 1474072.8146 11417773.0084) (list 1474065.4769 11417122.6452) (list 1474065.4785 11417115.2950) (list 1474065.8561 11417100.4680) (list 1474066.7238 11417085.7025) (list 1474068.0811 11417070.9748) (list 1474068.9320 11417063.7155) (list 1474071.0181 11417049.0712) (list 1474073.5898 11417034.5023) (list 1474075.0749 11417027.1705) (list 1474076.6444 11417020.0254) (list 1474080.1781 11417005.6584) (list 1474084.1873 11416991.4158) (list 1474086.3950 11416984.2672) (list 1474088.6661 11416977.3176) (list 1474093.6135 11416963.3674) (list 1474099.0192 11416949.5942) (list 1474104.8797 11416936.0067) (list 1474108.0135 11416929.2147) (list 1474111.1877 11416922.6217) (list 1474117.9358 11416909.4547) (list 1474125.1173 11416896.5189) (list 1474132.7249 11416883.8275) (list 1474136.7337 11416877.5050) (list 1474140.7492 11416871.3964) (list 1474149.1822 11416859.2384) (list 1474158.0107 11416847.3720) (list 1474167.2315 11416835.8015) (list 1474172.0351 11416830.0759) (list 1474176.8365 11416824.5381) (list 1474186.8222 11416813.5878) (list 1474197.8392 11416802.2975) (list 1474182.2477 11416786.8508) (list 1474175.6978 11416793.4621) (list 1474166.1116 11416803.6281) (list 1474159.8961 11416810.5547) (list 1474150.8163 11416821.1983) (list 1474144.9564 11416828.4282) (list 1474136.4274 11416839.5008) (list 1474130.9330 11416847.0122) (list 1474122.9601 11416858.5028) (list 1474117.8480 11416866.2794) (list 1474110.4622 11416878.1476) (list 1474105.7425 11416886.1685) (list 1474098.9526 11416898.3942) (list 1474094.6393 11416906.6408) (list 1474088.4708 11416919.1835) (list 1474084.5719 11416927.6339) (list 1474079.0306 11416940.4752) (list 1474075.5590 11416949.1099) (list 1474070.6685 11416962.2024) (list 1474067.6287 11416970.9984) (list 1474063.3913 11416984.3286) (list 1474060.7957 11416993.2657) (list 1474057.2315 11417006.7799) (list 1474055.0818 11417015.8346) (list 1474052.1917 11417029.5197) (list 1474049.2242 11417046.3247) (list 1474047.2500 11417060.1684) (list 1474046.1666 11417069.4115) (list 1474044.8855 11417083.3367) (list 1474044.2646 11417092.6224) (list 1474043.6786 11417106.5842)))
  (pvSegT "SEG 13 - CT-7 WEST (2 OF 2)" (list 1474023.0820 11417393.3846) 1.55950687 7.0)
  (pvSegT "850 MODULES = 170 TABLES = 527.0 kWp" (list 1474032.5814 11417393.2774) 1.55950687 5.5))
(defun pvSeg14 ()
  (pvSegPL (list (list 1474199.7134 11418281.2266) (list 1474180.1320 11418291.1396) (list 1474503.9883 11418930.8575) (list 1474523.5696 11418920.9446)))
  (pvSegT "SEG 14 - CT-8 NORTH-WEST" (list 1474321.0972 11418621.6111) 1.10216249 7.0)
  (pvSegT "485 MODULES = 97 TABLES = 300.7 kWp" (list 1474329.5729 11418617.3203) 1.10216249 5.5))
(defun pvSegTable ()
  (pvSegPL (list (list 1482056.00 11416475.00) (list 1484085.50 11416475.00) (list 1484085.50 11415784.00) (list 1482056.00 11415784.00)))
  (pvSegTL "SOLAR PV L5 - MODULES PER SEGMENT (NEW SEGMENT WHERE THE PANEL RUN IS BROKEN)" 1482100.00 11416420.00 30.80)
  (pvSegTL "SEG" 1482100.00 11416375.00 22.00)
  (pvSegTL "AREA / RUN" 1482230.00 11416375.00 22.00)
  (pvSegTL "MODULES" 1483000.00 11416375.00 22.00)
  (pvSegTL "TABLES" 1483280.00 11416375.00 22.00)
  (pvSegTL "kWp" 1483530.00 11416375.00 22.00)
  (pvSegTL "LENGTH" 1483780.00 11416375.00 22.00)
  (pvSegTL "01" 1482100.00 11416337.60 22.00)
  (pvSegTL "CT-1 NORTH A" 1482230.00 11416337.60 22.00)
  (pvSegTL "1250" 1483000.00 11416337.60 22.00)
  (pvSegTL "250" 1483280.00 11416337.60 22.00)
  (pvSegTL "775.0" 1483530.00 11416337.60 22.00)
  (pvSegTL "~1858 FT" 1483780.00 11416337.60 22.00)
  (pvSegTL "02" 1482100.00 11416300.20 22.00)
  (pvSegTL "CT-2 NORTH-EAST" 1482230.00 11416300.20 22.00)
  (pvSegTL "180" 1483000.00 11416300.20 22.00)
  (pvSegTL "36" 1483280.00 11416300.20 22.00)
  (pvSegTL "111.6" 1483530.00 11416300.20 22.00)
  (pvSegTL "~265 FT" 1483780.00 11416300.20 22.00)
  (pvSegTL "03" 1482100.00 11416262.80 22.00)
  (pvSegTL "CT-3 EAST" 1482230.00 11416262.80 22.00)
  (pvSegTL "670" 1483000.00 11416262.80 22.00)
  (pvSegTL "134" 1483280.00 11416262.80 22.00)
  (pvSegTL "415.4" 1483530.00 11416262.80 22.00)
  (pvSegTL "~988 FT" 1483780.00 11416262.80 22.00)
  (pvSegTL "04" 1482100.00 11416225.40 22.00)
  (pvSegTL "CT-4 SOUTH-EAST CURVE (1/3)" 1482230.00 11416225.40 22.00)
  (pvSegTL "215" 1483000.00 11416225.40 22.00)
  (pvSegTL "43" 1483280.00 11416225.40 22.00)
  (pvSegTL "133.3" 1483530.00 11416225.40 22.00)
  (pvSegTL "~319 FT" 1483780.00 11416225.40 22.00)
  (pvSegTL "05" 1482100.00 11416188.00 22.00)
  (pvSegTL "CT-4 SOUTH-EAST CURVE (2/3)" 1482230.00 11416188.00 22.00)
  (pvSegTL "615" 1483000.00 11416188.00 22.00)
  (pvSegTL "123" 1483280.00 11416188.00 22.00)
  (pvSegTL "381.3" 1483530.00 11416188.00 22.00)
  (pvSegTL "~925 FT" 1483780.00 11416188.00 22.00)
  (pvSegTL "06" 1482100.00 11416150.60 22.00)
  (pvSegTL "CT-4 SOUTH-EAST CURVE (3/3)" 1482230.00 11416150.60 22.00)
  (pvSegTL "310" 1483000.00 11416150.60 22.00)
  (pvSegTL "62" 1483280.00 11416150.60 22.00)
  (pvSegTL "192.2" 1483530.00 11416150.60 22.00)
  (pvSegTL "~464 FT" 1483780.00 11416150.60 22.00)
  (pvSegTL "07" 1482100.00 11416113.20 22.00)
  (pvSegTL "CT-5 SOUTH ARC" 1482230.00 11416113.20 22.00)
  (pvSegTL "465" 1483000.00 11416113.20 22.00)
  (pvSegTL "93" 1483280.00 11416113.20 22.00)
  (pvSegTL "288.3" 1483530.00 11416113.20 22.00)
  (pvSegTL "~695 FT" 1483780.00 11416113.20 22.00)
  (pvSegTL "08" 1482100.00 11416075.80 22.00)
  (pvSegTL "CT-6 SOUTH (1/3)" 1482230.00 11416075.80 22.00)
  (pvSegTL "125" 1483000.00 11416075.80 22.00)
  (pvSegTL "25" 1483280.00 11416075.80 22.00)
  (pvSegTL "77.5" 1483530.00 11416075.80 22.00)
  (pvSegTL "~184 FT" 1483780.00 11416075.80 22.00)
  (pvSegTL "09" 1482100.00 11416038.40 22.00)
  (pvSegTL "CT-6 SOUTH (2/3)" 1482230.00 11416038.40 22.00)
  (pvSegTL "560" 1483000.00 11416038.40 22.00)
  (pvSegTL "112" 1483280.00 11416038.40 22.00)
  (pvSegTL "347.2" 1483530.00 11416038.40 22.00)
  (pvSegTL "~826 FT" 1483780.00 11416038.40 22.00)
  (pvSegTL "10" 1482100.00 11416001.00 22.00)
  (pvSegTL "CT-6 SOUTH (3/3)" 1482230.00 11416001.00 22.00)
  (pvSegTL "235" 1483000.00 11416001.00 22.00)
  (pvSegTL "47" 1483280.00 11416001.00 22.00)
  (pvSegTL "145.7" 1483530.00 11416001.00 22.00)
  (pvSegTL "~346 FT" 1483780.00 11416001.00 22.00)
  (pvSegTL "11" 1482100.00 11415963.60 22.00)
  (pvSegTL "CT-9 SOUTH-WEST" 1482230.00 11415963.60 22.00)
  (pvSegTL "695" 1483000.00 11415963.60 22.00)
  (pvSegTL "139" 1483280.00 11415963.60 22.00)
  (pvSegTL "430.9" 1483530.00 11415963.60 22.00)
  (pvSegTL "~1025 FT" 1483780.00 11415963.60 22.00)
  (pvSegTL "12" 1482100.00 11415926.20 22.00)
  (pvSegTL "CT-7 WEST (1/2)" 1482230.00 11415926.20 22.00)
  (pvSegTL "260" 1483000.00 11415926.20 22.00)
  (pvSegTL "52" 1483280.00 11415926.20 22.00)
  (pvSegTL "161.2" 1483530.00 11415926.20 22.00)
  (pvSegTL "~384 FT" 1483780.00 11415926.20 22.00)
  (pvSegTL "13" 1482100.00 11415888.80 22.00)
  (pvSegTL "CT-7 WEST (2/2)" 1482230.00 11415888.80 22.00)
  (pvSegTL "850" 1483000.00 11415888.80 22.00)
  (pvSegTL "170" 1483280.00 11415888.80 22.00)
  (pvSegTL "527.0" 1483530.00 11415888.80 22.00)
  (pvSegTL "~1267 FT" 1483780.00 11415888.80 22.00)
  (pvSegTL "14" 1482100.00 11415851.40 22.00)
  (pvSegTL "CT-8 NORTH-WEST" 1482230.00 11415851.40 22.00)
  (pvSegTL "485" 1483000.00 11415851.40 22.00)
  (pvSegTL "97" 1483280.00 11415851.40 22.00)
  (pvSegTL "300.7" 1483530.00 11415851.40 22.00)
  (pvSegTL "~715 FT" 1483780.00 11415851.40 22.00)
  (pvSegTL "TOTAL (14 SEGMENTS)" 1482230.00 11415814.00 22.00)
  (pvSegTL "6,915" 1483000.00 11415814.00 22.00)
  (pvSegTL "1,383" 1483280.00 11415814.00 22.00)
  (pvSegTL "4,287.3" 1483530.00 11415814.00 22.00))
(defun c:PVSEGMENTS ( / oldcmd olderr ss n)
  (setq oldcmd (getvar "CMDECHO")) (setvar "CMDECHO" 0)
  (setq olderr *error*)
  (defun *error* (msg) (command "_.UNDO" "_E") (setvar "CMDECHO" oldcmd) (setq *error* olderr)
    (princ (strcat "\nPVSEGMENTS error: " msg)) (princ))
  (command "_.UNDO" "_BE")
  (if (setq ss (ssget "_X" '((8 . "PV-SEG-OUTLINE,PV-SEG-TEXT")))) (command "_.ERASE" ss ""))
  (pvSegLayer "PV-SEG-OUTLINE" 6) (pvSegLayer "PV-SEG-TEXT" 6)
  (pvSeg01) (pvSeg02) (pvSeg03) (pvSeg04) (pvSeg05) (pvSeg06) (pvSeg07) (pvSeg08) (pvSeg09) (pvSeg10) (pvSeg11) (pvSeg12) (pvSeg13) (pvSeg14)
  (pvSegTable)
  (command "_.UNDO" "_E")
  (setvar "CMDECHO" oldcmd) (setq *error* olderr)
  (setq n (if (setq ss (ssget "_X" '((0 . "INSERT") (8 . "PV-MODULES")))) (sslength ss) 0))
  (if (/= n 6915)
    (princ (strcat "\nNOTE: layer PV-MODULES has " (itoa n) " panels, the labels are for the 6915-panel L5 layout. Run PVLAYOUT from PV_LAYOUT_L5_BLUE_LINE.lsp first.")))
  (princ "\nPVSEGMENTS labelled 14 segments, 6915 modules.  SEG 01: 1250 | SEG 02: 180 | SEG 03: 670 | SEG 04: 215 | SEG 05: 615 | SEG 06: 310 | SEG 07: 465 | SEG 08: 125 | SEG 09: 560 | SEG 10: 235 | SEG 11: 695 | SEG 12: 260 | SEG 13: 850 | SEG 14: 485")
  (princ))
(princ "\nPV segment labels loaded. Command: PVSEGMENTS")
(princ)
